(defun c:draw-tangents (/ sel-obj curves tangents inter-pt)
  (setq sel-obj (ssget '((0 . "LWPOLYLINE"))))
  (if sel-obj
    (progn
      (setq curves (list))
      (setq tangents (list))
      (repeat (sslength sel-obj)
        (setq obj (ssname sel-obj (setq i (1+ i))))
        (if (and (= "LWPOLYLINE" (cdr (assoc 0 (entget obj)))))
          (setq curves (cons obj curves))))
      (if curves
        (progn
          (repeat (length curves)
            (setq ent curves)
            (setq ent-length (cdr (assoc 90 (entget ent)))))
            (setq last-point (cdr (assoc 10 (entget (entlast ent))))))
            (while (setq ent (entnext ent))
              (cond ((null ent) nil)
                    ((= (cdr (assoc 0 (entget ent))) "VERTEX")
                      (setq ent-length (- ent-length (distance (cdr (assoc 10 (entget ent))) last-point)))
                      (setq last-point (cdr (assoc 10 (entget ent))))))))
              (setq curves (cdr curves)))
              (setq tangent (list))
              (setq last-pt (cdr (assoc 10 (entget (car curves)))))
              (repeat (length curves)
                (setq cur-obj (car curves))
                (setq cur-verts (vl-remove-if-not '(lambda (x) (= "VERTEX" (cdr (assoc 0 (entget x))))) (entget cur-obj)))
                (setq cur-verts (reverse cur-verts))
                (setq prev-pt last-pt)
                (while cur-verts
                  (setq pt (cdr (assoc 10 (car cur-verts))))
                  (setq tan (angle (mapcar '- pt prev-pt)))
                  (setq tangent (cons tan tangent))
                  (setq prev-pt pt)
                  (setq cur-verts (cdr cur-verts)))
                (setq curves (cdr curves))
                (setq last-pt prev-pt))
              (setq inter-pt (apply 'angle tangent))
              (setq inter-pt (polar (cdr (assoc 10 (entget (car curves))))) inter-pt ent-length))
              (command "._point" inter-pt)
              (princ "\n Tangent intersection point drawn.")
            (princ "\n No valid LWPOLYLINE objects selected."))
          (princ "\n No LWPOLYLINE objects selected."))
(defun c:draw-tangents (/ ss i ent verts pt1 pt2 ang)
  (setq ss (ssget '((0 . "LWPOLYLINE"))))
  (if ss
    (progn
      (repeat (setq i (sslength ss))
        (setq i (1- i)
              ent (ssname ss i)
              verts (vlax-get-property (vlax-ename->vla-object ent) 'coordinates)
              ang (angle
                    (trans (nth 0 verts) 0 1)
                    (trans (nth 1 verts) 0 1)
                    (trans (nth 2 verts) 0 1)
                  )
              pt1 (trans (nth 0 verts) 0 1)
              pt2 (trans (nth 1 verts) 0 1)
            )
        (command "._line" pt1 (polar pt1 (+ ang (/ pi 2)) 10.0))
        (command "._line" pt2 (polar pt2 (+ ang (/ pi 2)) 10.0))
      )
      (princ "\nTangents drawn successfully.")
    )
    (princ "\nNo LWPOLYLINE objects found.")
  )
)

(command "_.load" "C:\Program Files\Autodesk\AutoCAD 2016\Support\myplugin.lsp")
(defun c:draw-tangents (/)
  ; your code here
)
